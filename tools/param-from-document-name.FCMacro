# -*- coding: utf-8 -*-

# Macro Begin: /home/aea/.FreeCAD/Macro/param-from-document-name.FCMacro +++++++++++++++++++++++++++++++++++++++++++++++++
import FreeCAD
import re 

sheet = App.ActiveDocument.getObjectsByLabel('params')[0]
doc_name = App.ActiveDocument.Label
sheet.set('B1', doc_name)

# 2x20-male-pin-header.fcstd
regex_pattern = re.compile(sheet.get('B2'))
regex_search = regex_pattern.search(doc_name)

if regex_search:
	x_repeat = regex_search.group(1)
	y_repeat = regex_search.group(2)
	sheet.set('B3', '=%s' % x_repeat)
	sheet.set('B4', '=%s' % y_repeat)

App.ActiveDocument.recompute()
